# -*- coding: utf-8 -*-

# Macro Begin: C:\Users\Jorge\Documents\FreeCAD\Materiais\Cozinhas\MCL001.FCMacro +++++++++++++++++++++++++++++++++++++++++++++++++
import FreeCAD
import PartDesignGui
import Part

#Gui.activateWorkbench("PartDesignWorkbench")
App.newDocument("Sem nome")
#App.setActiveDocument("Sem_nome")
#App.ActiveDocument=App.getDocument("Sem_nome")
#Gui.ActiveDocument=Gui.getDocument("Sem_nome")
#Gui.activateWorkbench("PartWorkbench")
App.ActiveDocument.addObject("Part::Box","Box")
App.ActiveDocument.ActiveObject.Label = "Cubo"
App.ActiveDocument.recompute()
#Gui.SendMsgToActiveView("ViewFit")
#Gui.ActiveDocument.setEdit('Box',0)
#Gui.activeDocument().activeView().viewAxonometric()
FreeCAD.getDocument("Sem_nome").getObject("Box").Length = '5 mm'
FreeCAD.getDocument("Sem_nome").getObject("Box").Length = '50 mm'
FreeCAD.getDocument("Sem_nome").getObject("Box").Length = '503 mm'
FreeCAD.getDocument("Sem_nome").getObject("Box").Width = '1 mm'
FreeCAD.getDocument("Sem_nome").getObject("Box").Width = '16 mm'
FreeCAD.getDocument("Sem_nome").getObject("Box").Height = '5 mm'
FreeCAD.getDocument("Sem_nome").getObject("Box").Height = '56 mm'
FreeCAD.getDocument("Sem_nome").getObject("Box").Height = '563 mm'
#Gui.SendMsgToActiveView("ViewSelection")
#Gui.SendMsgToActiveView("Save")
App.getDocument("Sem_nome").saveAs(u"C:/Users/Jorge/Documents/FreeCAD/Materiais/Cozinhas/MCL001.FCStd")
# Macro End: C:\Users\Jorge\Documents\FreeCAD\Materiais\Cozinhas\MCL001.FCMacro +++++++++++++++++++++++++++++++++++++++++++++++++
